module sonic-device_neighbor {

    yang-version 1.1;

    namespace "http://github.com/sonic-net/sonic-device_neighbor";
    prefix device_neighbor;

    import ietf-inet-types {
        prefix inet;
    }

    import sonic-port {
        prefix port;
        revision-date 2026-09-23;
    }

    description "DEVICE_NEIGHBOR YANG Module for SONiC OS";

    revision 2026-09-23 {
        description "Import the sonic-port revision without the mode leaf.";
    }

    revision 2020-04-10 {
        description "First Revision";
    }

    container sonic-device_neighbor {

        container DEVICE_NEIGHBOR {

            description "Directly connected neighbor devices with hostname and port mapping";

            list DEVICE_NEIGHBOR_LIST {

                key "peer_name";

                leaf peer_name {
                    description "Key identifying the neighbor device entry";
                    type string {
                        length 1..255;
                    }
                }

                leaf name {
                    description "Hostname of the neighbor device";
                    type string {
                        length 1..255;
                    }
                }

                leaf mgmt_addr {
                    description "Management IP address of the neighbor device";
                    type inet:ip-address;
                }

                leaf local_port {
                    description "Local port connected to the neighbor device";
                    type leafref {
                        path /port:sonic-port/port:PORT/port:PORT_LIST/port:name;
                    }
                }

                leaf port {
                    description "Port on the neighbor device connected to the local port";
                    type string {
                        length 1..255;
                    }
                }

                leaf type {
                    description "Type of the neighbor device";
                    type string {
                        length 1..255;
                    }
                }
            }
            /* end of list DEVICE_NEIGHBOR_LIST */
        }
        /* end of container DEVICE_NEIGHBOR */
	}
	/* end of top level container */
}
/* end of module sonic-device_neighbor */
