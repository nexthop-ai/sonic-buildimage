module sonic-events-dhcp-relay {
    namespace "http://github.com/sonic-net/sonic-events-dhcp-relay";
    yang-version 1.1;
    prefix events-dhcp-relay;

    import sonic-events-common {
        prefix evtcmn;
        revision-date 2022-12-01;
    }

    organization
        "SONiC";

    contact
        "SONiC";

    description
        "SONIC dhcp-relay events";

    revision 2022-12-01 {
        description "dhcp-relay alert events.";
    }

    container sonic-events-dhcp-relay {
        container dhcp-relay-discard {
            evtcmn:ALARM_SEVERITY_MAJOR;

            description "
                Declares an event for dhcp-relay discarding packet on an
                interface due to missing IP address assigned.
                Params:
                    name of the interface discarding.";

            leaf ifname {
                type string {
                    pattern '[a-zA-Z0-9]+';
                }
                description "Name of the i/f discarding";
            }

            uses evtcmn:sonic-events-cmn;
        }

        container dhcp-relay-disparity {
            evtcmn:ALARM_SEVERITY_MAJOR;

            description "
                Declares an event for disparity detected in
                DHCP Relay behavior by dhcpmon.
                parameters:
                    vlan that shows this disparity
                    The duration of disparity";

            leaf vlan {
                type string {
                    pattern '(Agg-Vlan|Vlan)([0-9]{1,3}|[1-3][0-9]{3}|[4][0][0-8][0-9]|[4][0][9][0-4])';
                }
                description "Name of the vlan affected";
            }

            leaf duration {
                type uint32;
                description "Duration of disparity";
            }

            uses evtcmn:sonic-events-cmn;
        }

        container dhcp-relay-bind-failure {
            evtcmn:ALARM_SEVERITY_MAJOR;

            description "
                Declares an event for socket binding failure.
                parameters:
                    vlan that shows this failure
                    type either local or global";

            leaf vlan {
                type string {
                    pattern 'Vlan([0-9]{1,3}|[1-3][0-9]{3}|[4][0][0-8][0-9]|[4][0][9][0-4])';
                }
                description "Name of the vlan affected";
            }

            leaf type {
                type enumeration {
                    enum "local";
                    enum "global";
                }
                description "Address type";
            }

            uses evtcmn:sonic-events-cmn;
        }

        container dhcp-relay-send-failure {
            evtcmn:ALARM_SEVERITY_MAJOR;

            description "
                Declares an event for DHCP relay send failure.
                Params:
                    protocol - DHCPv4 or DHCPv6
                    downlink - client-side interface
                    uplink - server-side interface
                    dest_ip - destination IP of the failed send
                    vrf - VRF context
                    reason - send failure reason";

            leaf protocol {
                type string {
                    pattern 'DHCPv[46]';
                }
                description "DHCP protocol version";
            }

            leaf downlink {
                type string {
                    pattern '[a-zA-Z0-9_.-]+';
                }
                description "Client-side interface";
            }

            leaf uplink {
                type string {
                    pattern '[a-zA-Z0-9_.-]+';
                }
                description "Server-side interface";
            }

            leaf dest_ip {
                type string;
                description "Destination IP address of the failed send (server, or client on reply paths)";
            }

            leaf vrf {
                type string {
                    pattern '[a-zA-Z0-9_-]+';
                }
                description "VRF context";
            }

            leaf reason {
                type string;
                description "Send failure reason";
            }

            uses evtcmn:sonic-events-cmn;
        }
    }
}
