module sonic-port-qos-map {

    yang-version 1.1;

    namespace "http://github.com/sonic-net/sonic-port-qos-map";

    prefix pqm;

    import sonic-port {
        prefix prt;
    }

    import sonic-tc-priority-group-map {
        prefix tpgm;
    }

    import sonic-tc-queue-map {
        prefix tqm;
    }

    import sonic-pfc-priority-queue-map {
        prefix ppqm;
    }

    import sonic-pfc-priority-priority-group-map {
        prefix pppgm;
    }

    import sonic-dscp-tc-map {
        prefix dtm;
    }

    import sonic-dot1p-tc-map {
        prefix dot1ptm;
    }

    import sonic-scheduler {
        prefix sch;
    }

    import sonic-tc-dscp-map {
        prefix tdm;
    }

    import sonic-tc-dot1p-map {
        prefix tdot1pm;
    }

    organization
        "SONiC";

    contact
        "SONiC";

    description
        "SONIC PORT_QOS_MAP";

    revision 2019-05-15 {
        description
            "Initial revision.";
    }

    container sonic-port-qos-map {

        container PORT_QOS_MAP {
            list PORT_QOS_MAP_LIST {

                key "ifname";

                leaf ifname {
                    type union {
                        type string {
                            pattern "global";
                        }
                        type leafref {
                            path "/prt:sonic-port/prt:PORT/prt:PORT_LIST/prt:name";
                        }
                    }
                    description
                        "Reference of port or global on which QOS MAPS to be configured.";
                }

                leaf tc_to_pg_map {
                    type leafref {
                        path "/tpgm:sonic-tc-priority-group-map/tpgm:TC_TO_PRIORITY_GROUP_MAP/tpgm:TC_TO_PRIORITY_GROUP_MAP_LIST/tpgm:name";
                    }
                }

                leaf tc_to_queue_map {
                    type leafref {
                        path "/tqm:sonic-tc-queue-map/tqm:TC_TO_QUEUE_MAP/tqm:TC_TO_QUEUE_MAP_LIST/tqm:name";
                    }
                }

                leaf pfc_enable {
                    type string {
                        pattern "([0-7](,[0-7])*)?";
                    }
                    description
                        "Specify the queue(s) on which PFC is enabled. Empty string is allowed to disable PFC on all queues.";
                }

                leaf pfcwd_sw_enable {
                    type string {
                        pattern "([0-7](,[0-7])*)?";
                    }
                    description
                        "Specify the queue(s) on which software pfc watchdog are enabled. Empty string is allowed to disable watchdog on all queues.";
                }

                leaf pfc_to_queue_map {
                    type leafref {
                        path "/ppqm:sonic-pfc-priority-queue-map/ppqm:MAP_PFC_PRIORITY_TO_QUEUE/ppqm:MAP_PFC_PRIORITY_TO_QUEUE_LIST/ppqm:name";
                    }
                }

                leaf pfc_to_pg_map {
                    type leafref {
                        path "/pppgm:sonic-pfc-priority-priority-group-map/pppgm:PFC_PRIORITY_TO_PRIORITY_GROUP_MAP/pppgm:PFC_PRIORITY_TO_PRIORITY_GROUP_MAP_LIST/pppgm:name";
                    }
                }

                leaf dscp_to_tc_map {
                    type leafref {
                        path "/dtm:sonic-dscp-tc-map/dtm:DSCP_TO_TC_MAP/dtm:DSCP_TO_TC_MAP_LIST/dtm:name";
                    }
                }

                leaf tc_to_dscp_map {
                    type leafref {
                        path "/tdm:sonic-tc-dscp-map/tdm:TC_TO_DSCP_MAP/tdm:TC_TO_DSCP_MAP_LIST/tdm:name";
                    }
                }


                leaf dot1p_to_tc_map {
                    type leafref {
                        path "/dot1ptm:sonic-dot1p-tc-map/dot1ptm:DOT1P_TO_TC_MAP/dot1ptm:DOT1P_TO_TC_MAP_LIST/dot1ptm:name";
                    }
                }

                leaf tc_to_dot1p_map {
                    type leafref {
                        path "/tdot1pm:sonic-tc-dot1p-map/tdot1pm:TC_TO_DOT1P_MAP/tdot1pm:TC_TO_DOT1P_MAP_LIST/tdot1pm:name";
                    }
                }

                leaf scheduler {
                    type leafref {
                        path "/sch:sonic-scheduler/sch:SCHEDULER/sch:SCHEDULER_LIST/sch:name"; //Reference to SCHEDULER table
                    }
                    description "Scheduler for port.";
                }
            }
        }
    }
}
