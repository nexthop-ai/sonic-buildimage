module sonic-routing-policy-sets {
    namespace "http://github.com/sonic-net/sonic-routing-policy-lists";
    prefix rpolsets;
    yang-version 1.1;

    import ietf-inet-types {
        prefix inet;
    }

    import sonic-extension {
        prefix ext;
    }

    organization
        "SONiC";

    contact
        "SONiC";

    description
        "SONiC ROUTING POLICY SETS";

    revision 2021-02-26 {
        description
            "Initial revision.";
    }

    typedef routing-policy-action-type {
        type enumeration {
            enum permit {
                description "Permit action.";
            }
            enum deny {
                description "Deny action.";
            }
        }
        description
            "Routing policy action type permit or deny";
    }

    typedef ext-community-value-type {
        type union {
            type string {
                pattern 'route-target:.+';
            }
            type string {
                pattern 'route-origin:.+';
            }
            type string {
                pattern 'color:(00|01|10|11):(429496729[0-5]|42949672[0-8][0-9]|'
                +   '4294967[0-1][0-9]{2}|429496[0-6][0-9]{3}|'
                +   '42949[0-5][0-9]{4}|4294[0-8][0-9]{5}|'
                +   '429[0-3][0-9]{6}|42[0-8][0-9]{7}|'
                +   '4[0-1][0-9]{8}|[1-3][0-9]{9}|'
                +   '[1-9][0-9]{0,8})';
            }
            type string {
                pattern 'none';
            }
        }
        description
            "Extended community value, one of:
             - route-target:ASN_OR_IPADDR:VALUE (route-target)
             - route-origin:ASN_OR_IPADDR:VALUE (route-origin / site-of-origin)
             - color:CC:VALUE, where CC is a 2-bit binary color 00/01/10/11 and
               VALUE is bounded to uint32 max, per RFC 9012
             - 'none', only valid as the sole member of a set-side leaf-list, to
               clear all previously-set extended communities.
             ASN_OR_IPADDR may be a plain AS number, AS-dot notation, or an IPv4
             address, matching FRR's 'ASN:NN_OR_IP-ADDRESS:NN' extended-community
             grammar -- deliberately left format-unconstrained here (beyond the
             keyword prefix) because FRR's own frr-bgp-route-map.yang types
             extcommunity-rt/extcommunity-soo as plain string for the same
             reason: no single regex cleanly covers ASN / AS-dot / IPv4-address
             without risking false rejection of values FRR itself accepts.";
    }

    grouping prefix-common-fields {
        leaf name {
            type leafref {
                path "../../../PREFIX_SET/PREFIX_SET_LIST/name";
            }
            description "Prefix name";
        }

        leaf ip_prefix {
            /* TODO - Validate ip-prefix based on PREFIX_SET/mode */
            type inet:ip-prefix;
            description
                "The prefix member in CIDR notation -- while the
                prefix may be either IPv4 or IPv6, most
                implementations require all members of the prefix set
                to be the same address family.  Mixing address types in
                the same prefix set is likely to cause an error.";
        }

        leaf masklength_range {
            type string;
            description
                "Defines a range for the masklength, or 'exact' if
                the prefix has an exact length.

                Example: 10.3.192.0/21 through 10.3.192.0/24 would be
                expressed as prefix: 10.3.192.0/21,
                          masklength_range: 21..24.

                              Example: 10.3.192.0/21 would be expressed as
                              prefix: 10.3.192.0/21,
                          masklength_range: exact";
        }

        leaf action {
            type routing-policy-action-type;
            description
                "Permit/Deny action for the prefix list.";
        }
    }

    container sonic-routing-policy-sets {

        container PREFIX_SET {

            list PREFIX_SET_LIST {
                key "name";

                leaf name {
                    type string;
                    description "Prefix name";
                }

                leaf mode {
                    type enumeration {
                        enum IPv4;
                        enum IPv6;
                    }
                    description "Address family of the prefix";
                    default "IPv4";
                }
            }
        }

        container PREFIX {

            list PREFIX_LIST {
                key "name sequence_number ip_prefix masklength_range";
                //ext:custom-validation ValidateIpPrefixListCfg;

                uses prefix-common-fields;

                leaf sequence_number {
                    type uint32 {
                        range "1..4294967295";
                    }
                    description
                        "The sequence number determines the order in which prefix-list entries are applied. It must
                         be unique for each prefix in a prefix-list. Target devices should apply the prefixes in
                         ascending order determined by sequence no (low to high), rather than relying only on order
                         in the list.";
                    must "count(../../PREFIX_LIST[name=current()/../name and sequence_number=current()]) <= 1" {
                        error-message "sequence_number required to be unique for each prefix-list";
                    }
                }
            }

            list PREFIX_NOSEQ_LIST {
                key "name ip_prefix masklength_range";
                //ext:custom-validation ValidateIpPrefixListCfg;

                uses prefix-common-fields;
            }
        }
        container COMMUNITY_SET {

            list COMMUNITY_SET_LIST {
                key "name";

                leaf name {
                    type string;
                    description "Community name";
                }

                leaf set_type {
                    type enumeration {
                        enum STANDARD;
                        enum EXPANDED;
                    }
                    description "Community type";
                }

                leaf match_action {
                    type enumeration {
                        enum ANY;
                        enum ALL;
                    }
                    description "Match action any/all";
                }

                leaf action {
                    type routing-policy-action-type;
                    description
                        "Permit/Deny action for the community";
                }

                leaf-list community_member {
                    type string;
                    ordered-by user;
                    description
                        "members of the community set.";
                }
            }
        }

        container EXTENDED_COMMUNITY_SET {

            list EXTENDED_COMMUNITY_SET_LIST {
                key "name";

                leaf name {
                    type string;
                    description "Extended community name";
                }

                leaf set_type {
                    type enumeration {
                        enum STANDARD;
                        enum EXPANDED;
                    }
                    description "Extended community type";
                }

                leaf match_action {
                    type enumeration {
                        enum ANY;
                        enum ALL;
                    }
                    description "Match action any/all";
                }

                leaf action {
                    type routing-policy-action-type;
                    description
                        "Permit/Deny action for the ext-community";
                }

                leaf-list community_member {
                    type string;
                    ordered-by user;
                    description
                        "members of the extended community set. For set_type STANDARD,
                        must follow ext-community-value-type's format: 'route-target:ASN_OR_IPADDR:VALUE',
                        'route-origin:ASN_OR_IPADDR:VALUE', or 'color:CC:VALUE' (CC is a 2-bit
                        binary color 00/01/10/11). For set_type EXPANDED, members are instead
                        raw POSIX-regex FRR CLI syntax (e.g. '_65000:1_', 'color 00:100') passed
                        through unparsed -- no format is enforced for EXPANDED members.";
                }
            }
        }

        container AS_PATH_SET {

            list AS_PATH_SET_LIST {
                key "name";

                leaf name {
                    type string;
                    description "AS PATH name";
                }

                leaf action {
                    type routing-policy-action-type;
                    description
                        "Permit/Deny action for the as-path-list.";
                }

                leaf-list as_path_set_member {
                    type string;
                    ordered-by user;
                    description
                        "AS path expression -- list of ASes in the set";
                }
            }
        }
    }
}
