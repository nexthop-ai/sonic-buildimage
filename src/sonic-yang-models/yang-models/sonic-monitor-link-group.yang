module sonic-monitor-link-group {

    yang-version 1.1;

    namespace "http://github.com/sonic-net/sonic-monitor-link-group";
    prefix mlg;

    organization
        "SONiC";

    contact
        "SONiC";

    description
        "SONIC monitor link group YANG Module for SONiC OS";

    revision 2025-12-02 {
        description
            "Initial revision for Monitor link Groups";
    }

    container sonic-monitor-link-group {

        container MONITOR_LINK_GROUP {

            description "Link State Tracking Group configuration";

            list MONITOR_LINK_GROUP_LIST {

                key "group_name";

                leaf group_name {
                    type string {
                        length "1..128";
                        pattern "[a-zA-Z0-9_-]+";
                    }
                    description "Name of the link state tracking group";
                }

                leaf-list uplinks {
                    type string {
                        pattern 'Ethernet([0-9]{1,3}|[1-9][0-9]{3})|PortChannel[0-9]+';
                    }
                    description "List of uplink interfaces for this monitor link group";
                }

                leaf-list downlinks {
                    type string {
                        pattern 'Ethernet([0-9]{1,3}|[1-9][0-9]{3})|PortChannel[0-9]+';
                    }
                    description "List of downlink interfaces for this monitor link group";
                }

                leaf description {
                    type string {
                        length "1..255";
                    }
                    description "Description of the link state tracking group";
                }

                leaf startup-delay {
                    type uint32 {
                        range 0..6000;
                    }
                    default "0";
                    description "Time in seconds to elapse before bringing up the downlink (max 6000)";
                }

                leaf min-uplinks {
                    type uint32 {
                        range 0..512;
                    }
                    default "1";
                    description "Minimum number of uplinks that must be operational for the group to be considered up (max 512)";
                }
            }
            /* end of list MONITOR_LINK_GROUP_LIST */
        }
        /* end of container MONITOR_LINK_GROUP */
    }
    /* end of container sonic-monitor-link-group */
}
