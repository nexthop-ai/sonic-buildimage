module test-yang-structure {

  namespace "http://github.com/sonic-net/test";
  prefix yangstructtest;

  yang-version 1.1;

  import ietf-yang-types {
    prefix yang;
  }

  import ietf-inet-types {
    prefix inet;
  }

  import test-head {
    prefix head;
    revision-date 2019-07-01;
  }

  revision 2021-10-30 {
    description "First Revision";
  }

  container test-yang-structure {

    container YANG_STRUCT_TEST {

      description "sample test container";

      list YANG_LIST_TEST_LIST {

        key "name";

        leaf name {
          type string;
        }

        leaf-list leaf-list-test {
          description "Test leaf-list statement";
          type inet:ipv6-address;
        }

        container container-in-list-test {
          leaf leaf-1 {
            description "test leaf in container";
            type string {
              pattern "down|up";
            }
          }

          leaf leaf-2 {
            description "test leaf in container";
            type string;
          }

          choice multi-choice-in-container-test-1 {
            case mc-case-test-1 {
              leaf mc-case-leaf-1 {
                description "test leaf in multi choice";
                type uint32;
              }
            }

            case mc-case-test-2 {
              leaf mc-case-leaf-2 {
                description "test leaf in multi choice";
                type uint8;
              }
            }
          }

          choice multi-choice-in-container-test-2 {
            case mc-case-test-3 {
              leaf mc-case-leaf-3 {
                description "test leaf in multi choice";
                type uint16;
              }
            }
          }
        }

        choice single-choice-in-list-test {
          case case-test-1 {
            leaf case-leaf-1 {
              description "test leaf in single choice";
              type uint32;
            }
          }

          case case-test-2 {
            leaf case-leaf-2 {
              description "test leaf in single choice";
              type uint16;
            }
          }
        }
      }
      /* end of YANG_LIST_TEST_LIST */
    }
    /* end of container YANG_STRUCT_TEST */

    container CONTAINER_AND_LIST_TEST {

      description "table with a global-settings container next to a keyed list";

      container Global {
        leaf src_ip {
          type inet:ip-address;
        }

        leaf retry_interval {
          type uint32;
        }
      }

      list CONTAINER_AND_LIST_TEST_LIST {

        key "prefix name";

        leaf prefix {
          type string {
            pattern "Subscription|DestinationGroup";
          }
        }

        leaf name {
          type string;
        }

        leaf dst_addr {
          type string;
        }
      }
      /* end of CONTAINER_AND_LIST_TEST_LIST */
    }
    /* end of container CONTAINER_AND_LIST_TEST */
  }
  /* end of container test-yang-container */
}
/* end of module test-yang-structure */
